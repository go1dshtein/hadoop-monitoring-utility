SUBAGENT-SHELL-HADOOP-MIB DEFINITIONS ::= BEGIN

IMPORTS
  MODULE-IDENTITY, enterprises, Counter32, Counter64, Gauge32, Integer32 FROM SNMPv2-SMI
  functionsEntry FROM SUBAGENT-SHELL-MIB
  TimeStamp FROM SNMPv2-TC;

SUBAGENT-SHELL-HADOOP MODULE-IDENTITY
  LAST-UPDATED "201512111034Z"
  ORGANIZATION "Example org"
  CONTACT-INFO "goldshtein.kirill@gmail.com"
  DESCRIPTION "SNMP SUBAGENT SHELL HADOOP STATS MIB"
  ::= { functionsEntry 15 }

  hadoopStatsFuncTime OBJECT-TYPE
    SYNTAX      OCTET STRING
    MAX-ACCESS  read-only
    STATUS      current
    DESCRIPTION "response time, ms"
    ::= { SUBAGENT-SHELL-HADOOP 1 }

  hadoopStatsFuncResult OBJECT-TYPE
    SYNTAX      Gauge32
    MAX-ACCESS  read-only
    STATUS      current
    DESCRIPTION "return code"
    ::= { SUBAGENT-SHELL-HADOOP 2 }

  hadoop OBJECT IDENTIFIER ::= { SUBAGENT-SHELL-HADOOP 3 }

  {% for key, value in objects.items() -%}

  {% if value.name %}
  {{key[1]}} OBJECT-TYPE
    SYNTAX      {{value.type}}
    MAX-ACCESS  read-only
    STATUS      current
    {%- if value.description -%}DESCRIPTION "{{value.description}}"{% endif %}
    ::= { {{key[0]}} {{value.oid}} }
  {% else %}
  {{key[1]}} OBJECT IDENTIFIER ::= { {{key[0]}} {{value.oid}} }
  {% endif %}

  {%- endfor %}

END
